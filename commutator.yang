module mobilenetwork {
	namespace "mobilenetwork";
	prefix "network";

	container subscribers {
		list subscriber {
	    	key "number";
	    	leaf number {
				type string;
			}
	    	leaf userName {
				type string;
				config false;
	 		}
			leaf incomingNumber {
				type string;
	 		}
			leaf state {
				type enumeration {
					enum idle;
					enum busy;
					enum active;
				}
				default "idle";
			}
		}
	}
}
