module commutator {
	namespace "commutator";
	prefix "test";

	container subscribers {
		list subscriber {
	    	key "number";
	    	leaf number {
				type string {
         			length "3..4";
         			pattern '\+?[0-9]*';
     			}
			}
	    	leaf userName {
				type string;
				config false;
	 		}
			leaf incomingNumber {
				type string;
	 		}
			leaf state {
				type enumeration {
					enum idle;
					enum busy;
					enum active;
				}
				default "idle";
			}
		}
	}
	notification statCall {
        leaf startTime {
            type string;
            mandatory true;
        }
        leaf abonentA {
            type string;
            mandatory true;
        }
        leaf abonentB {
            type string;
            mandatory true;
        }
        leaf duration {
            type string;
        }
    }
}
